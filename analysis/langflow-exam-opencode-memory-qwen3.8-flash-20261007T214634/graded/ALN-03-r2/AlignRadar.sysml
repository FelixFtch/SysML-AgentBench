package AlignRadar {
    public import UavSensorSpec::*;
    public import RadarVendor::*;

    alias SearchRadar for RadarVendor::RadarModule_def;
    alias Camera for RadarVendor::GimbalCamera_def;
    alias rangeKm for RadarVendor::RadarModule_def::maxRangeKm;

    allocation searchRadarAlloc allocate UavSensorSpec::uav.searchRadar to RadarVendor::payload.radar;
    allocation eoCameraAlloc allocate UavSensorSpec::uav.eoCamera to RadarVendor::payload.gimbal;
}
