// READ ONLY: named product facts. No hardware or parser test claimed.
package PerceptionOffer {
 private import HardwareOffers::*;
 part def OfferedLidar :> Mid360S;
 part def OfferedDepthCamera :> D435i;
}
